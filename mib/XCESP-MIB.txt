XCESP-MIB DEFINITIONS ::= BEGIN

--
-- XCESP router product MIB — sub-tree under IKATA-SNMP-MIB
-- (ikataSnmp = enterprises.43978).
--
-- 0.2.19 — minimum vertical slice: one scalar (xcespServerName) and
-- one notification (xcespColdStart).  Subsequent releases grow this
-- file (or replace it with auto-generator output from gen-xcesp-mib.py
-- in 0.2.21+).
--

IMPORTS
    MODULE-IDENTITY, OBJECT-TYPE, NOTIFICATION-TYPE,
    enterprises
        FROM SNMPv2-SMI
    DisplayString
        FROM SNMPv2-TC
    ifIndex
        FROM IF-MIB;

ikataSnmp           OBJECT IDENTIFIER ::= { enterprises 43978 }
ikataSnmpObjects    OBJECT IDENTIFIER ::= { ikataSnmp 1 }

xcespMib MODULE-IDENTITY
    LAST-UPDATED "202606060000Z"
    ORGANIZATION "www.ikatanetworks.com"
    CONTACT-INFO "email: contact@ikatanetworks.com"
    DESCRIPTION
        "XCESP router product MIB.  Exposes router-level state through
         the AgentX subagent embedded in xcespserver.  Polled values are
         backed by ServerStatus paths; notifications fire on state
         transitions captured by the EventDispatcher."
    REVISION     "202606060000Z"
    DESCRIPTION
        "0.2.19 — initial release: xcespServerName scalar + xcespColdStart
         notification.  Subsequent releases will add IF-MIB ifTable bridge
         (0.2.20) and broader schema-derived objects (0.2.21+)."
    ::= { ikataSnmpObjects 1 }

--
-- Scalar objects
--

xcespObjects        OBJECT IDENTIFIER ::= { xcespMib 1 }
xcespNotifications  OBJECT IDENTIFIER ::= { xcespMib 0 }

xcespServerName OBJECT-TYPE
    SYNTAX       DisplayString
    MAX-ACCESS   read-only
    STATUS       current
    DESCRIPTION
        "Operator-configured XCESP system name (management/system/name).
         When unset by the operator, defaults to the server's hostname."
    ::= { xcespMib 1 }

--
-- xcespIfTable — per-interface mapping back to (router, vrf, name).
-- Indexed by IF-MIB::ifIndex so it joins naturally with ifTable rows.
-- Lets NMS pollers slice XCESP's flat ifTable by router and/or VRF.
--

xcespIfTable OBJECT-TYPE
    SYNTAX       SEQUENCE OF XcespIfEntry
    MAX-ACCESS   not-accessible
    STATUS       current
    DESCRIPTION
        "Table mapping IF-MIB::ifIndex values to the (router, vrf,
         xcesp-interface-name) tuple that XCESP uses internally.  One
         row per interface; one ifIndex per row.  Pollers walk the
         standard IF-MIB::ifTable for traffic and admin/oper data,
         then snmpget rows from xcespIfTable to learn which router and
         VRF each interface belongs to."
    ::= { xcespMib 2 }

xcespIfEntry OBJECT-TYPE
    SYNTAX       XcespIfEntry
    MAX-ACCESS   not-accessible
    STATUS       current
    DESCRIPTION  "One row per XCESP interface, indexed by ifIndex."
    INDEX        { ifIndex }
    ::= { xcespIfTable 1 }

XcespIfEntry ::= SEQUENCE {
    xcespIfRouter      DisplayString,
    xcespIfVrf         DisplayString,
    xcespIfXcespName   DisplayString,
    xcespIfType        DisplayString
}

xcespIfRouter OBJECT-TYPE
    SYNTAX       DisplayString
    MAX-ACCESS   read-only
    STATUS       current
    DESCRIPTION  "Name of the XCESP router that owns this interface."
    ::= { xcespIfEntry 1 }

xcespIfVrf OBJECT-TYPE
    SYNTAX       DisplayString
    MAX-ACCESS   read-only
    STATUS       current
    DESCRIPTION  "Name of the VRF inside the router that owns this interface."
    ::= { xcespIfEntry 2 }

xcespIfXcespName OBJECT-TYPE
    SYNTAX       DisplayString
    MAX-ACCESS   read-only
    STATUS       current
    DESCRIPTION
        "Interface name as XCESP knows it (e.g. `loHA`, `rlHA_XX`,
         `greHA`).  Same value that appears in `show interface` CLI
         output and in xcespserver.conf."
    ::= { xcespIfEntry 3 }

xcespIfType OBJECT-TYPE
    SYNTAX       DisplayString
    MAX-ACCESS   read-only
    STATUS       current
    DESCRIPTION
        "XCESP's own interface-type tag (device, loopback, rlink, gre,
         vlan, bridge, l2tp, vxlan, xfrm).  More descriptive than
         IF-MIB::ifType for XCESP-specific tunnel/virtual types.  In
         xcespserver 0.2.11 this field is a placeholder ('unknown')
         pending xcesp-on-rtr emitting the IFACE_TYPE into ServerStatus
         in 0.2.23."
    ::= { xcespIfEntry 4 }

--
-- Notifications
--

xcespColdStart NOTIFICATION-TYPE
    STATUS       current
    DESCRIPTION
        "Fired once when xcespserver starts and successfully registers
         with the master snmpd over AgentX.  Carries the standard
         snmpTrapOID varbind identifying this notification."
    ::= { xcespNotifications 1 }

END
